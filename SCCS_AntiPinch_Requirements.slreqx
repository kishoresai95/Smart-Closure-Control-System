# SCCS_AntiPinch_Requirements

## REQ-001: REQ-001: Anti-pinch current spike detection response time (Functional)
The anti-pinch system shall detect a motor current spike above the threshold and transition to the REVERSING state within 100ms.
